; GeoBIM borehole strata solid generator for AutoCAD/Civil 3D
; Load with APPLOAD, then run command: GEOBIM_SOLIDS
(vl-load-com)
(defun geobim-ensure-layer (name color / doc layers layer)
  (setq doc (vla-get-ActiveDocument (vlax-get-acad-object)))
  (setq layers (vla-get-Layers doc))
  (if (tblsearch "LAYER" name)
    (setq layer (vla-item layers name))
    (setq layer (vla-add layers name))
  )
  (vla-put-Color layer color)
  layer
)
(defun geobim-add-cylinder (layer color x y z radius height / doc ms obj)
  (geobim-ensure-layer layer color)
  (setq doc (vla-get-ActiveDocument (vlax-get-acad-object)))
  (setq ms (vla-get-ModelSpace doc))
  (setq obj (vla-AddCylinder ms (vlax-3d-point x y (+ z (/ height 2.0))) radius height))
  (vla-put-Layer obj layer)
  (vla-put-Color obj color)
  obj
)
(defun c:GEOBIM_SOLIDS (/ oldcmdecho)
  (setq oldcmdecho (getvar "CMDECHO"))
  (setvar "CMDECHO" 0)
  (geobim-ensure-layer "STRATUM_SOFT_ROCK" 94)
  (geobim-ensure-layer "STRATUM_SOIL" 43)
  (geobim-ensure-layer "STRATUM_WEATHERED_ROCK" 41)
  (geobim-add-cylinder "STRATUM_SOFT_ROCK" 94 184771.4590 548451.8659 -12.9700 1.5000 5.0000)
  (geobim-add-cylinder "STRATUM_SOFT_ROCK" 94 184961.2036 548667.7699 15.1000 1.5000 2.0000)
  (geobim-add-cylinder "STRATUM_SOFT_ROCK" 94 184982.3674 549179.3099 30.4500 1.5000 2.3000)
  (geobim-add-cylinder "STRATUM_SOFT_ROCK" 94 185017.3836 549219.3246 27.4500 1.5000 1.9000)
  (geobim-add-cylinder "STRATUM_SOIL" 43 184434.5629 548403.2556 11.2000 1.5000 16.0000)
  (geobim-add-cylinder "STRATUM_SOIL" 43 184459.1161 548403.2097 13.3000 1.5000 14.0000)
  (geobim-add-cylinder "STRATUM_SOIL" 43 184521.9149 548503.7588 16.5000 1.5000 12.0000)
  (geobim-add-cylinder "STRATUM_SOIL" 43 184554.6840 548511.3894 17.4000 1.5000 10.0000)
  (geobim-add-cylinder "STRATUM_SOIL" 43 184570.3845 548499.0183 13.8000 1.5000 13.0000)
  (geobim-add-cylinder "STRATUM_SOIL" 43 184625.6889 548524.4542 10.0000 1.5000 13.0000)
  (geobim-add-cylinder "STRATUM_SOIL" 43 184766.5900 548476.4810 -5.2000 1.5000 22.0000)
  (geobim-add-cylinder "STRATUM_SOIL" 43 184771.4590 548451.8659 -0.9700 1.5000 18.0000)
  (geobim-add-cylinder "STRATUM_SOIL" 43 184823.8195 548462.5471 -1.7900 1.5000 18.0000)
  (geobim-add-cylinder "STRATUM_SOIL" 43 184961.2036 548667.7699 17.1000 1.5000 18.0000)
  (geobim-add-cylinder "STRATUM_SOIL" 43 184982.3674 549179.3099 37.5500 1.5000 5.4000)
  (geobim-add-cylinder "STRATUM_SOIL" 43 185017.3836 549219.3246 42.0500 1.5000 10.4000)
  (geobim-add-cylinder "STRATUM_SOIL" 43 185029.1994 548203.6388 -16.9000 1.5000 16.9000)
  (geobim-add-cylinder "STRATUM_SOIL" 43 185033.8981 548177.1819 -15.0000 1.5000 15.0000)
  (geobim-add-cylinder "STRATUM_WEATHERED_ROCK" 41 184434.5629 548403.2556 6.2000 1.5000 5.0000)
  (geobim-add-cylinder "STRATUM_WEATHERED_ROCK" 41 184459.1161 548403.2097 8.3000 1.5000 5.0000)
  (geobim-add-cylinder "STRATUM_WEATHERED_ROCK" 41 184521.9149 548503.7588 10.5000 1.5000 6.0000)
  (geobim-add-cylinder "STRATUM_WEATHERED_ROCK" 41 184554.6840 548511.3894 -2.6000 1.5000 20.0000)
  (geobim-add-cylinder "STRATUM_WEATHERED_ROCK" 41 184570.3845 548499.0183 -3.2000 1.5000 17.0000)
  (geobim-add-cylinder "STRATUM_WEATHERED_ROCK" 41 184625.6889 548524.4542 5.0000 1.5000 5.0000)
  (geobim-add-cylinder "STRATUM_WEATHERED_ROCK" 41 184766.5900 548476.4810 -10.2000 1.5000 5.0000)
  (geobim-add-cylinder "STRATUM_WEATHERED_ROCK" 41 184771.4590 548451.8659 -7.9700 1.5000 7.0000)
  (geobim-add-cylinder "STRATUM_WEATHERED_ROCK" 41 184823.8195 548462.5471 -6.7900 1.5000 5.0000)
  (geobim-add-cylinder "STRATUM_WEATHERED_ROCK" 41 184982.3674 549179.3099 32.7500 1.5000 4.8000)
  (geobim-add-cylinder "STRATUM_WEATHERED_ROCK" 41 185017.3836 549219.3246 29.3500 1.5000 12.7000)
  (geobim-add-cylinder "STRATUM_WEATHERED_ROCK" 41 185029.1994 548203.6388 -20.0000 1.5000 3.1000)
  (geobim-add-cylinder "STRATUM_WEATHERED_ROCK" 41 185033.8981 548177.1819 -18.0000 1.5000 3.0000)
  (setvar "CMDECHO" oldcmdecho)
  (princ "\nGeoBIM solids created: 31")
  (princ)
)
(princ "\nGeoBIM loaded. Run GEOBIM_SOLIDS to create 3D solids.")
(princ)
